X680-13-Sub1 DEFINITIONS ::=
BEGIN

EXPORTS
    TestEnumeratedType1, TestEnumeratedType2, testInteger1, testInteger2;

TestEnumeratedType1 ::= ENUMERATED {
    a, b, c
}

TestEnumeratedType2 ::= ENUMERATED {
    d, e, f
}

testInteger1 INTEGER ::= 4711

testInteger2 INTEGER ::= 4712

END
