X680-13 DEFINITIONS ::=
BEGIN

IMPORTS
    TestEnumeratedType1, testInteger1
        FROM X680-13-Sub1;

TestEnumeratedType4 ::= TestEnumeratedType1

TestEnumeratedType5 ::= X680-13-Sub1.TestEnumeratedType2

TestEnumeratedType6 ::= X680-13-Sub2.TestEnumeratedType3

TestSequence1 ::= SEQUENCE {
   a INTEGER DEFAULT testInteger1,
   b INTEGER DEFAULT X680-13-Sub1.testInteger2,
   c INTEGER DEFAULT X680-13-Sub2.testInteger3
}

END
