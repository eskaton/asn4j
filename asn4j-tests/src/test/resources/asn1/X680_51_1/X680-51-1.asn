X680-51-1 DEFINITIONS ::=
BEGIN

testBitString1 BIT STRING ::= '001'B

TestBitString1 ::= BIT STRING ((ALL EXCEPT '011'B) ^ (SIZE(3..3)))
TestBitString2 ::= BIT STRING ((SIZE(1..2)) | '111'B)
TestBitString3 ::= BIT STRING (INCLUDES TestBitString2 | '000'B)
TestBitString4 ::= BIT STRING ('000'B | '001'B | '010'B, ...)
TestBitString5 ::= BIT STRING (INCLUDES TestBitString4 EXCEPT '010'B)
TestBitString6 ::= BIT STRING (INCLUDES BIT STRING EXCEPT '010'B)
TestBitString7 ::= BIT STRING (ALL EXCEPT testBitString1)

TestBoolean1 ::= BOOLEAN (TRUE | FALSE)
TestBoolean2 ::= BOOLEAN (INCLUDES TestBoolean1 EXCEPT TRUE)

TestEnumeration1 ::= ENUMERATED {
        a, b, c, ..., d(4), e, f
}

TestEnumeration2 ::= TestEnumeration1 ((c | d | e) ^ (d | e | f))
TestEnumeration3 ::= TestEnumeration1 (ALL EXCEPT (c | d))
TestEnumeration4 ::= TestEnumeration1 (TestEnumeration2 EXCEPT e)

testInteger1 INTEGER ::= 3
testInteger2 INTEGER ::= 4

TestNamedInteger1 ::= INTEGER {
	value1(1), value2(testInteger2)
}

TestInteger1 ::= INTEGER (ALL EXCEPT 0)
TestInteger2 ::= INTEGER (ALL EXCEPT (-1..1))
TestInteger3 ::= INTEGER ((0..2) | (4..6) | 9)
TestInteger4 ::= TestInteger3 (MIN<..5)
TestInteger5 ::= TestInteger3 (5..<MAX)
TestInteger6 ::= INTEGER (TestInteger4 ^ (4 | 5 | 6))
TestInteger7 ::= INTEGER (TestInteger6 EXCEPT 4)
TestInteger8 ::= TestInteger5 (ALL EXCEPT 5)
TestInteger9 ::= INTEGER (ALL EXCEPT testInteger1)
TestInteger10 ::= TestNamedInteger1 (ALL EXCEPT value1)
TestInteger11 ::= TestNamedInteger1 (ALL EXCEPT value2)

TestNull1 ::= NULL (NULL)
TestNull2 ::= NULL (TestNull1 EXCEPT NULL)

TestObjectIdentifier1 ::= OBJECT IDENTIFIER ({ 0 3 6 3 } | { 0 3 6 4 })
TestObjectIdentifier2 ::= OBJECT IDENTIFIER (TestObjectIdentifier1 EXCEPT { itu-t 3 6 4})

TestRelativeOID1 ::= RELATIVE-OID ({ 3 6 3 } | { 3 6 4 })
TestRelativeOID2 ::= RELATIVE-OID (TestRelativeOID1 EXCEPT { 3 6 4})

TestOidIri1 ::= OID-IRI ("/ISO/a/b/a" | "/ISO/a/b/b")
TestOidIri2 ::= OID-IRI (TestOidIri1 EXCEPT "/ISO/a/b/a")

TestRelativeOidIri1 ::= RELATIVE-OID-IRI ("a/b/a" | "a/b/b")
TestRelativeOidIri2 ::= RELATIVE-OID-IRI (TestRelativeOidIri1 EXCEPT "a/b/a")

testOctetString1 OCTET STRING ::= '0F'H

TestOctetString1 ::= OCTET STRING ((ALL EXCEPT '010203'H) ^ (SIZE(3..3)))
TestOctetString2 ::= OCTET STRING ((SIZE(1..2)) | '010203'H)
TestOctetString3 ::= OCTET STRING (INCLUDES TestOctetString2 | '0A0B0C'H)
TestOctetString4 ::= OCTET STRING ('00'H | '0F'H | 'F0'H, ...)
TestOctetString5 ::= OCTET STRING (INCLUDES TestOctetString4 EXCEPT 'F0'H)
TestOctetString6 ::= OCTET STRING (INCLUDES OCTET STRING EXCEPT 'F0'H)
TestOctetString7 ::= OCTET STRING (ALL EXCEPT testOctetString1)

TestSequence1 ::= SEQUENCE {
    a VisibleString (SIZE(1..2)),
    b INTEGER (1 | 2 | 3)
}

TestSetOf1 ::= SET (ALL EXCEPT {1}) OF INTEGER
TestSetOf2 ::= SET (({1}) | SIZE(2)) OF INTEGER
TestSetOf3 ::= SET (INCLUDES TestSetOf2 EXCEPT {1}) OF INTEGER
TestSetOf4 ::= SET SIZE (2) OF SET SIZE (1..2) OF INTEGER
TestSetOf5 ::= SET SIZE (2) OF INTEGER (1..2)
TestSetOf6 ::= SET SIZE (2) OF BIT STRING (SIZE (3))
TestSetOf7 ::= SET SIZE (1) OF INTEGER (1..2)
TestSetOf8 ::= SET OF INTEGER (1..2)
TestSetOf9 ::= SET OF INTEGER (1..5) (2..3)
TestSetOf10 ::= SET OF SET OF INTEGER (1..2)

TestSequenceOf1 ::= SEQUENCE SIZE (2) OF SET SIZE (1..2) OF INTEGER
TestSequenceOf2 ::= TestSequenceOf1

TestChoice1 ::= CHOICE {
    a BOOLEAN (TRUE),
    b INTEGER (1)
}
TestChoice2 ::= CHOICE {
    a BIT STRING (SIZE(1..2) | '111'B),
    b BOOLEAN (TRUE),
    c TestEnumeration1 (a | b),
    d INTEGER (1 | 2 | 3),
    e OCTET STRING (SIZE(1) | '01FF'H),
    f VisibleString (SIZE(1..2)),
    g GeneralString (SIZE(1..2)),
    h GraphicString (SIZE(1..2)),
    i IA5String (SIZE(1..2)),
    j VideotexString (SIZE(1..2)),
    k TeletexString (SIZE(1..2)),
    l PrintableString (SIZE(1..2)),
    m NumericString (SIZE(1..2)),
    n UTF8String (SIZE(1..2)),
    o UniversalString (SIZE(1..2)),
    p BMPString (SIZE(1..2)),
    q SEQUENCE (SIZE (1..2)) OF INTEGER (3..4)
}

testVisibleString1 VisibleString ::= "xyz"

TestVisibleString1 ::= VisibleString ((SIZE (1..3) ^ FROM ("a".."f")) | testVisibleString1)

testISO646String1 ISO646String ::= "xyz"

TestISO646String1 ::= ISO646String ((SIZE (1..3) ^ FROM ("a".."f")) | testISO646String1)

testGeneralString1 GeneralString ::= "xyz"

TestGeneralString1 ::= GeneralString ((SIZE (1..3) ^ FROM ("a".."f")) | testGeneralString1)

testGraphicString1 GraphicString ::= "xyz"

TestGraphicString1 ::= GraphicString ((SIZE (1..3) ^ FROM ("a".."f")) | testGraphicString1)

testIA5String1 IA5String ::= "xyz"

TestIA5String1 ::= IA5String ((SIZE (1..3) ^ FROM ("a".."f")) | testIA5String1)

testVideotexString1 VideotexString ::= "xyz"

TestVideotexString1 ::= VideotexString ((SIZE (1..3) ^ FROM ("a".."f")) | testVideotexString1)

testTeletexString1 TeletexString ::= "xyz"

TestTeletexString1 ::= TeletexString ((SIZE (1..3) ^ FROM ("a".."f")) | testTeletexString1)

testT61String1 T61String ::= "xyz"

TestT61String1 ::= T61String ((SIZE (1..3) ^ FROM ("a".."f")) | testT61String1)

testPrintableString1 PrintableString ::= "xyz"

TestPrintableString1 ::= PrintableString ((SIZE (1..3) ^ FROM ("a".."f")) | testPrintableString1)

testNumericString1 NumericString ::= "456"

TestNumericString1 ::= NumericString ((SIZE (1..3) ^ FROM ("1".."3")) | testNumericString1)

testUTF8String1 UTF8String ::= "xyz"

TestUTF8String1 ::= UTF8String ((SIZE (1..3) ^ FROM ("a".."f")) | testUTF8String1)

testUniversalString1 UniversalString ::= "xyz"

TestUniversalString1 ::= UniversalString ((SIZE (1..3) ^ FROM ("a".."f")) | testUniversalString1)

testBMPString1 BMPString ::= "xyz"

TestBMPString1 ::= BMPString ((SIZE (1..3) ^ FROM ("a".."f")) | testBMPString1)

END
