X680-51-1 DEFINITIONS ::=
BEGIN

testBitString1 BIT STRING ::= '001'B

TestBitString1 ::= BIT STRING ((ALL EXCEPT '011'B) ^ (SIZE(3..3)))
TestBitString2 ::= BIT STRING ((SIZE(1..2)) | '111'B)
TestBitString3 ::= BIT STRING (INCLUDES TestBitString2 | '000'B)
TestBitString4 ::= BIT STRING ('000'B | '001'B | '010'B, ...)
TestBitString5 ::= BIT STRING (INCLUDES TestBitString4 EXCEPT '010'B)
TestBitString6 ::= BIT STRING (INCLUDES BIT STRING EXCEPT '010'B)
TestBitString7 ::= BIT STRING (ALL EXCEPT testBitString1)

TestBoolean1 ::= BOOLEAN (TRUE | FALSE)
TestBoolean2 ::= BOOLEAN (INCLUDES TestBoolean1 EXCEPT TRUE)

TestEnumeration1 ::= ENUMERATED {
        a, b, c, ..., d(4), e, f
}

TestEnumeration2 ::= TestEnumeration1 ((c | d | e) ^ (d | e | f))
TestEnumeration3 ::= TestEnumeration1 (ALL EXCEPT (c | d))
TestEnumeration4 ::= TestEnumeration1 (TestEnumeration2 EXCEPT e)

testInteger1 INTEGER ::= 3
testInteger2 INTEGER ::= 4

TestNamedInteger1 ::= INTEGER {
	value1(1), value2(testInteger2)
}

TestInteger1 ::= INTEGER (ALL EXCEPT 0)
TestInteger2 ::= INTEGER (ALL EXCEPT (-1..1))
TestInteger3 ::= INTEGER ((0..2) | (4..6) | 9)
TestInteger4 ::= TestInteger3 (MIN<..5)
TestInteger5 ::= TestInteger3 (5..<MAX)
TestInteger6 ::= INTEGER (TestInteger4 ^ (4 | 5 | 6))
TestInteger7 ::= INTEGER (TestInteger6 EXCEPT 4)
TestInteger8 ::= TestInteger5 (ALL EXCEPT 5)
TestInteger9 ::= INTEGER (ALL EXCEPT testInteger1)
TestInteger10 ::= TestNamedInteger1 (ALL EXCEPT value1)
TestInteger11 ::= TestNamedInteger1 (ALL EXCEPT value2)

TestNull1 ::= NULL (NULL)
TestNull2 ::= NULL (TestNull1 EXCEPT NULL)

TestObjectIdentifier1 ::= OBJECT IDENTIFIER ({ 0 3 6 3 } | { 0 3 6 4 })
TestObjectIdentifier2 ::= OBJECT IDENTIFIER (TestObjectIdentifier1 EXCEPT { itu-t 3 6 4})

TestRelativeOID1 ::= RELATIVE-OID ({ 3 6 3 } | { 3 6 4 })
TestRelativeOID2 ::= RELATIVE-OID (TestRelativeOID1 EXCEPT { 3 6 4})

TestOidIri1 ::= OID-IRI ("/ISO/a/b/a" | "/ISO/a/b/b")
TestOidIri2 ::= OID-IRI (TestOidIri1 EXCEPT "/ISO/a/b/a")

END
