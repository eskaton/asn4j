X680-51-3 DEFINITIONS ::=
BEGIN

TestBitString1 ::= BIT STRING ('000'B | '001'B | '010'B, ...)
TestBitString2 ::= BIT STRING (INCLUDES TestBitString1)
TestBitString3 ::= BIT STRING (INCLUDES TestBitString1, ...)
TestBitString4 ::= BIT STRING (INCLUDES BIT STRING)

TestBoolean1 ::= BOOLEAN (TRUE)
TestBoolean2 ::= BOOLEAN (INCLUDES TestBoolean1)

TestEnumeration1 ::= ENUMERATED {
        a, b, c, d
}

TestEnumeration2 ::= TestEnumeration1 (TestEnumeration1 EXCEPT a)

TestInteger1 ::= INTEGER (1 | 2 | 4)
TestInteger2 ::= INTEGER (INCLUDES TestInteger1)

TestNull1 ::= NULL
TestNull2 ::= NULL (INCLUDES TestNull1)
TestNull3 ::= NULL (ALL EXCEPT NULL)
TestNull4 ::= NULL (INCLUDES TestNull3)
TestNull5 ::= NULL (NULL)
TestNull6 ::= NULL (INCLUDES TestNull5)

testObjectIdentifier1 OBJECT IDENTIFIER ::= { itu-t 3 }
testObjectIdentifier2 OBJECT IDENTIFIER ::= { testObjectIdentifier1 6 2 }

TestObjectIdentifier1 ::= OBJECT IDENTIFIER ({ 0 3 6 1 } | testObjectIdentifier2)
TestObjectIdentifier2 ::= OBJECT IDENTIFIER (INCLUDES TestObjectIdentifier1)

testRelativeOID1 RELATIVE-OID ::= { 7 3 }
testRelativeOID2 RELATIVE-OID ::= { testRelativeOID1 6 2 }

TestRelativeOID1 ::= RELATIVE-OID ({ 7 3 6 1 } | testRelativeOID2)
TestRelativeOID2 ::= RELATIVE-OID (INCLUDES TestRelativeOID1)

testOidIri1 OID-IRI ::= "/ISO/a/b/a"
testOidIri2 OID-IRI ::= "/ISO/a/b/b"

TestOidIri1 ::= OID-IRI ("/ISO/a/b/a" | testOidIri2)
TestOidIri2 ::= OID-IRI (INCLUDES TestOidIri1)

END
