X680-51-3 DEFINITIONS ::=
BEGIN

TestBitString1 ::= BIT STRING ('000'B | '001'B | '010'B, ...)
TestBitString2 ::= BIT STRING (INCLUDES TestBitString1)
TestBitString3 ::= BIT STRING (INCLUDES TestBitString1, ...)
TestBitString4 ::= BIT STRING (INCLUDES BIT STRING)

TestBoolean1 ::= BOOLEAN (TRUE)
TestBoolean2 ::= BOOLEAN (INCLUDES TestBoolean1)

TestEnumeration1 ::= ENUMERATED {
        a, b, c, d, ...
}

TestEnumeration2 ::= TestEnumeration1 (TestEnumeration1 EXCEPT a)

TestEnumeration3 ::= ENUMERATED {
        a, b, c, ..., d
} (TestEnumeration1)

TestInteger1 ::= INTEGER (1 | 2 | 4)
TestInteger2 ::= INTEGER (INCLUDES TestInteger1)

TestNull1 ::= NULL
TestNull2 ::= NULL (INCLUDES TestNull1)
TestNull3 ::= NULL (ALL EXCEPT NULL)
TestNull4 ::= NULL (INCLUDES TestNull3)
TestNull5 ::= NULL (NULL)
TestNull6 ::= NULL (INCLUDES TestNull5)

testObjectIdentifier1 OBJECT IDENTIFIER ::= { itu-t 3 }
testObjectIdentifier2 OBJECT IDENTIFIER ::= { testObjectIdentifier1 6 2 }

TestObjectIdentifier1 ::= OBJECT IDENTIFIER ({ 0 3 6 1 } | testObjectIdentifier2)
TestObjectIdentifier2 ::= OBJECT IDENTIFIER (INCLUDES TestObjectIdentifier1)

testRelativeOID1 RELATIVE-OID ::= { 7 3 }
testRelativeOID2 RELATIVE-OID ::= { testRelativeOID1 6 2 }

TestRelativeOID1 ::= RELATIVE-OID ({ 7 3 6 1 } | testRelativeOID2)
TestRelativeOID2 ::= RELATIVE-OID (INCLUDES TestRelativeOID1)

testOidIri1 OID-IRI ::= "/ISO/a/b/a"
testOidIri2 OID-IRI ::= "/ISO/a/b/b"

TestOidIri1 ::= OID-IRI ("/ISO/a/b/a" | testOidIri2)
TestOidIri2 ::= OID-IRI (INCLUDES TestOidIri1)

testRelativeOidIri1 RELATIVE-OID-IRI ::= "a/b/a"
testRelativeOidIri2 RELATIVE-OID-IRI ::= "a/b/b"

TestRelativeOidIri1 ::= RELATIVE-OID-IRI ("a/b/a" | testRelativeOidIri2)
TestRelativeOidIri2 ::= RELATIVE-OID-IRI (INCLUDES TestRelativeOidIri1)
TestRelativeOidIri3 ::= TestRelativeOidIri2 ("a/b/b")

testOctetString1 OCTET STRING ::= '61AD'H

TestOctetString1 ::= OCTET STRING ('0101'B | testOctetString1)
TestOctetString2 ::= OCTET STRING (INCLUDES TestOctetString1)
TestOctetString3 ::= TestOctetString2 ('61AD'H)

TestSetOf1 ::= SET ({1} | {2} | {3}) OF INTEGER
TestSetOf2 ::= SET (INCLUDES TestSetOf1) OF INTEGER

TestSequenceOf1 ::= SEQUENCE ({1} | {2} | {3}) OF INTEGER
TestSequenceOf2 ::= SEQUENCE (INCLUDES TestSequenceOf1) OF TestInteger1

TestSet1 ::= SET {
    a TestInteger1,
    b BOOLEAN
} ({a 4, b TRUE})

TestSet2 ::= SET {
    a INTEGER,
    b BOOLEAN
} (TestSet1)

TestSequence1 ::= SEQUENCE {
    a TestInteger1,
    b BOOLEAN
} ({a 2, b FALSE})

TestSequence2 ::= SEQUENCE {
    a INTEGER,
    b BOOLEAN
} (TestSequence1)

TestChoice1 ::= CHOICE {
   a INTEGER,
   b BOOLEAN
} (a: 12)
TestChoice2 ::= CHOICE {
   a INTEGER,
   b BOOLEAN
} (TestChoice1)

TestVisibleString1 ::= VisibleString ("def")
TestVisibleString2 ::= VisibleString (TestVisibleString1)

TestISO646String1 ::= ISO646String ("def")
TestISO646String2 ::= ISO646String (TestISO646String1)

TestGeneralString1 ::= GeneralString ("efg")
TestGeneralString2 ::= GeneralString (TestGeneralString1)

TestGraphicString1 ::= GraphicString ("abc")
TestGraphicString2 ::= GraphicString (TestGraphicString1)

TestIA5String1 ::= IA5String ("abc")
TestIA5String2 ::= IA5String (TestIA5String1)

TestVideotexString1 ::= VideotexString ("abc")
TestVideotexString2 ::= VideotexString (TestVideotexString1)

TestTeletexString1 ::= TeletexString ("abc")
TestTeletexString2 ::= TeletexString (TestTeletexString1)

TestT61String1 ::= T61String ("abc")
TestT61String2 ::= T61String (TestT61String1)

TestPrintableString1 ::= PrintableString ("abc")
TestPrintableString2 ::= PrintableString (TestPrintableString1)

TestNumericString1 ::= NumericString ("123")
TestNumericString2 ::= NumericString (TestNumericString1)

TestUTF8String1 ::= UTF8String ("abc")
TestUTF8String2 ::= UTF8String (TestUTF8String1)

TestUniversalString1 ::= UniversalString ("abc")
TestUniversalString2 ::= UniversalString (TestUniversalString1)

TestBMPString1 ::= BMPString ("abc")
TestBMPString2 ::= BMPString (TestBMPString1)

END
