X680-51-8 DEFINITIONS ::=
BEGIN

TestSetOf1 ::= SET SIZE (1) OF INTEGER (0..4)
TestSetOf2 ::= TestSetOf1 (WITH COMPONENT (1..2))
TestSetOf3 ::= SET SIZE (1) OF SET OF INTEGER (0..4)
TestSetOf4 ::= TestSetOf3 (WITH COMPONENT (SIZE (2)))
TestSetOf5 ::= TestSetOf3 (WITH COMPONENT (WITH COMPONENT (1..2)))
TestSetOf6 ::= TestSetOf3 (WITH COMPONENT (SIZE (2) | (WITH COMPONENT (1..2))))
TestSetOf7 ::= TestSetOf3 (WITH COMPONENT (SIZE (2) ^ (WITH COMPONENT (1..2))))
TestSetOf8 ::= TestSetOf3 (WITH COMPONENT (SIZE (2) EXCEPT (WITH COMPONENT (1..2))))

TestSequenceOf1 ::= SEQUENCE SIZE (1) OF INTEGER (0..4)
TestSequenceOf2 ::= TestSequenceOf1 (WITH COMPONENT (1..2))

TestSequence1 ::= SEQUENCE {
    a INTEGER,
    b BOOLEAN,
    ...
}
TestSequence2 ::= TestSequence1 (WITH COMPONENTS {a (1..2), b (TRUE)})
TestSequence3 ::= SEQUENCE {
    c TestSequence2,
    ...,
    d BOOLEAN
} (WITH COMPONENTS {c (WITH COMPONENTS {a (1), b (TRUE)}), d (FALSE)})
TestSequence4 ::= SEQUENCE {
    c SEQUENCE {
        a INTEGER,
        b BOOLEAN,
        ...
    },
    ...,
    d BOOLEAN
} (WITH COMPONENTS {c (WITH COMPONENTS {a (1), b (TRUE)}), d (FALSE)})
TestSequence5 ::= SEQUENCE {
    c SEQUENCE {
        a INTEGER,
        b BOOLEAN,
        ...
    },
    ...,
    d BOOLEAN
} (WITH COMPONENTS {c (WITH COMPONENTS {a (1)})})
TestSequence6 ::= SEQUENCE {
    a INTEGER OPTIONAL,
    b BOOLEAN
} (WITH COMPONENTS {a ABSENT})
TestSequence7 ::= SEQUENCE {
    a INTEGER OPTIONAL,
    b BOOLEAN
} (WITH COMPONENTS {a PRESENT})
TestSequence8 ::= SEQUENCE {
    a INTEGER OPTIONAL,
    b BOOLEAN
} (WITH COMPONENTS {a OPTIONAL})

TestSet1 ::= SET {
    a INTEGER,
    b BOOLEAN
} (WITH COMPONENTS {b(TRUE), a (1)})

-- Test all types
TestSetOf109 ::= SET OF BOOLEAN
TestSetOf110 ::= TestSetOf109 (WITH COMPONENT (TRUE))
TestEnumerated1 ::= ENUMERATED {a, b, c}
TestSetOf111 ::= SET OF TestEnumerated1
TestSetOf112 ::= TestSetOf111 (WITH COMPONENT (a))
TestSetOf113 ::= SET OF NULL
TestSetOf114 ::= TestSetOf113 (WITH COMPONENT (NULL))
TestSetOf115 ::= SET OF OBJECT IDENTIFIER
TestSetOf116 ::= TestSetOf115 (WITH COMPONENT ({ 0 3 6 3 }))
TestSetOf117 ::= SET OF RELATIVE-OID
TestSetOf118 ::= TestSetOf117 (WITH COMPONENT ({ 3 6 3 }))
TestSetOf119 ::= SET OF OID-IRI
TestSetOf120 ::= TestSetOf119 (WITH COMPONENT ("/ISO/a/b/e"))
TestSetOf121 ::= SET OF RELATIVE-OID-IRI
TestSetOf122 ::= TestSetOf121 (WITH COMPONENT ("a/b/e"))
TestSetOf123 ::= SET OF OCTET STRING
TestSetOf124 ::= TestSetOf123 (WITH COMPONENT ('0101'B))
TestSetOf125 ::= SET OF BIT STRING
TestSetOf126 ::= TestSetOf125 (WITH COMPONENT ('0101'B))
TestSetOf127 ::= SET OF TestSequenceOf2
TestSetOf128 ::= TestSetOf127 (WITH COMPONENT (WITH COMPONENT (1)))
TestSetOf129 ::= SET OF TestSequence2
TestSetOf130 ::= TestSetOf129 (WITH COMPONENT ({ a 1, b TRUE }))
TestSetOf131 ::= SET OF TestChoice3
TestSetOf132 ::= TestSetOf131 (WITH COMPONENT (b: TRUE))

TestSequence105 ::= SEQUENCE {
    a ENUMERATED {a, b, c}
} (WITH COMPONENTS {a (a|b)})
TestSequence106 ::= SEQUENCE {
    a NULL
} (WITH COMPONENTS {a (NULL)})
TestSequence107 ::= SEQUENCE {
    a OBJECT IDENTIFIER
} (WITH COMPONENTS {a ({ 0 3 6 3 })})
TestSequence108 ::= SEQUENCE {
    a RELATIVE-OID
} (WITH COMPONENTS {a ({ 3 6 3 })})
TestSequence109 ::= SEQUENCE {
    a OID-IRI
} (WITH COMPONENTS {a ("/ISO/a/b/e")})
TestSequence110 ::= SEQUENCE {
    a RELATIVE-OID-IRI
} (WITH COMPONENTS {a ("a/b/e")})
TestSequence111 ::= SEQUENCE {
    a OCTET STRING
} (WITH COMPONENTS {a ('0101'B)})
TestSequence112 ::= SEQUENCE {
    a BIT STRING
} (WITH COMPONENTS {a ('0101'B)})
TestSequence113 ::= SEQUENCE {
    a TestSetOf1
} (WITH COMPONENTS {a (WITH COMPONENT (1..3))})
TestSequence114 ::= SEQUENCE {
    COMPONENTS OF TestSequence113
} (WITH COMPONENTS {a (WITH COMPONENT (1..2))})
TestSequence115 ::= SEQUENCE {
    a CHOICE {
        b INTEGER
    }
} (WITH COMPONENTS {a (WITH COMPONENTS {b (11)})})

TestChoice1 ::= CHOICE {
   a INTEGER,
   b BOOLEAN
} (WITH COMPONENTS {a (1), b (TRUE)})
TestChoice2 ::= CHOICE {
   a CHOICE {
      a INTEGER,
      b CHOICE {
         c BIT STRING
      }
   },
   b BOOLEAN
} (WITH COMPONENTS {a (WITH COMPONENTS {a (11), b (WITH COMPONENTS {c ('0101'B)})}), b (TRUE)})

TestChoice3 ::= CHOICE {
   a INTEGER,
   b BOOLEAN
} (WITH COMPONENTS {a ABSENT})

TestChoice4 ::= CHOICE {
   a INTEGER,
   b BOOLEAN
} (WITH COMPONENTS {a PRESENT})

END
