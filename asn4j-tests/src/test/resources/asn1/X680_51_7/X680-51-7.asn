X680-51-7 DEFINITIONS ::=
BEGIN

TestVisibleString1 ::= VisibleString (FROM ("a"|"b"|"c"))
TestVisibleString2 ::= VisibleString (FROM ("abc"))
TestVisibleString3 ::= VisibleString (FROM ("a"))
TestVisibleString4 ::= VisibleString (FROM ("a".."z"))
TestVisibleString5 ::= VisibleString (FROM ("a".."d" EXCEPT "c"))
TestVisibleString6 ::= VisibleString (FROM ("a".."d" | "x".."z"))
TestVisibleString7 ::= VisibleString (FROM ("a".."d" ^ "c".."f"))
TestVisibleString8 ::= VisibleString (FROM ("a"<..<"e") | "bf")
TestVisibleString9 ::= TestVisibleString8 (FROM ("c".."f"))

TestISO646String1 ::= ISO646String (FROM ("a"<..<"e") | "bf")
TestISO646String2 ::= TestISO646String1 (FROM ("c".."f"))

TestGeneralString1 ::= GeneralString (FROM ("a"<..<"e") | "bf")
TestGeneralString2 ::= TestGeneralString1 (FROM ("c".."f"))

TestGraphicString1 ::= GraphicString (FROM ("a"<..<"e") | "bf")
TestGraphicString2 ::= TestGraphicString1 (FROM ("c".."f"))

TestIA5String1 ::= IA5String (FROM ("a"<..<"e") | "bf")
TestIA5String2 ::= TestIA5String1 (FROM ("c".."f"))

TestVideotexString1 ::= VideotexString (FROM ("a"<..<"e") | "bf")
TestVideotexString2 ::= TestVideotexString1 (FROM ("c".."f"))

TestTeletexString1 ::= TeletexString (FROM ("a"<..<"e") | "bf")
TestTeletexString2 ::= TestTeletexString1 (FROM ("c".."f"))

TestT61String1 ::= T61String (FROM ("a"<..<"e") | "bf")
TestT61String2 ::= TestT61String1 (FROM ("c".."f"))

TestPrintableString1 ::= PrintableString (FROM ("a"<..<"e") | "bf")
TestPrintableString2 ::= TestPrintableString1 (FROM ("c".."f"))

TestNumericString1 ::= NumericString (FROM ("1"<..<"5") | "123")
TestNumericString2 ::= TestNumericString1 (FROM ("3".."7"))

TestUTF8String1 ::= UTF8String (FROM ("a"<..<"e") | "bf")
TestUTF8String2 ::= TestUTF8String1 (FROM ("c".."f"))

TestUniversalString1 ::= UniversalString (FROM ("a"<..<"e") | "bf")
TestUniversalString2 ::= TestUniversalString1 (FROM ("c".."f"))

TestBMPString1 ::= BMPString (FROM ("a"<..<"e") | "bf")
TestBMPString2 ::= TestBMPString1 (FROM ("c".."f"))

END
