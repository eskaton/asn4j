X690-8 DEFINITIONS ::=
BEGIN

-- 8.4
TestEnumeration ::= ENUMERATED {
	a(0), b(1), c(128)
}

-- 8.9
TestSequence ::= SEQUENCE {
    a [PRIVATE 3] EXPLICIT [2] IMPLICIT [APPLICATION 4] EXPLICIT VisibleString
}

-- 8.14
Type1 ::= VisibleString

Type2 ::= [APPLICATION 3] IMPLICIT Type1

Type3 ::= [2] Type2

Type4 ::= [APPLICATION 7] IMPLICIT Type3

Type5 ::= [4] Type2

Type6 ::= [APPLICATION 11] Type3

Type7 ::= [PRIVATE 3] EXPLICIT [2] IMPLICIT [APPLICATION 4] EXPLICIT VisibleString

SetType1 ::= SET OF VisibleString

SetType2 ::= [APPLICATION 1] IMPLICIT SetType1

SetType3 ::= [0] SetType2

END
