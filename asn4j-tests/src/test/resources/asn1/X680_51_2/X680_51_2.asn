X680-51-2 DEFINITIONS ::=
BEGIN

bitStringValue BIT STRING ::= '100'B

TestBitString1 ::= BIT STRING (ALL EXCEPT bitStringValue)
TestBitString2 ::= BIT STRING (('000'B | '001'B | '010'B | '011'B | bitStringValue | '101'B | '110'B | '111'B) EXCEPT '010'B)
TestBitString3 ::= BIT STRING ((('000'B | '001'B | '010'B | '011'B) ^ ('001'B | '010'B | '011'B)) EXCEPT '010'B)
TestBitString4 ::= BIT STRING (('000'B | '001'B | '010'B) ^ ('001'B | '010'B), ...)
-- TestBitString5 must be extensible
TestBitString5 ::= TestBitString4
-- TestBitString6 must not be extensible
TestBitString6 ::= TestBitString4 (ALL EXCEPT '001'B)

TestBoolean1 ::= BOOLEAN (ALL EXCEPT TRUE)
TestBoolean2 ::= BOOLEAN (TRUE)
TestBoolean3 ::= BOOLEAN (FALSE)
TestBoolean4 ::= BOOLEAN (TRUE | FALSE)
TestBoolean5 ::= BOOLEAN ((TRUE | FALSE) ^ TRUE)
TestBoolean6 ::= TestBoolean4 (ALL EXCEPT FALSE)

TestEnumeration1 ::= ENUMERATED {
        a, b, c, d
}

TestEnumeration2 ::= TestEnumeration1 (a | b)
TestEnumeration3 ::= TestEnumeration1 ((a | b | c) ^ (b | c | d))
TestEnumeration4 ::= TestEnumeration1 (ALL EXCEPT d)

TestInteger1 ::= INTEGER (1 | 2)
TestInteger2 ::= INTEGER (ALL EXCEPT 0)
TestInteger3 ::= INTEGER (((1 | 2 | 3) ^ (2 | 3)) EXCEPT 3)

TestNull1 ::= NULL (NULL)
TestNull2 ::= NULL (ALL EXCEPT NULL)
TestNull3 ::= NULL ((NULL ^ NULL) EXCEPT NULL)

testObjectIdentifier1 OBJECT IDENTIFIER ::= { itu-t 4 }
testObjectIdentifier2 OBJECT IDENTIFIER ::= { testObjectIdentifier1 11 2 }

TestObjectIdentifier1 ::= OBJECT IDENTIFIER ({ 1 3 6 1 } | { 1 3 6 2 })
TestObjectIdentifier2 ::= OBJECT IDENTIFIER (({ 1 3 6 1 } | { 1 3 6 2 }) EXCEPT { 1 3 6 2 })
TestObjectIdentifier3 ::= OBJECT IDENTIFIER (({ 1 3 6 1 } | { 1 3 6 2 }) ^ { 1 3 6 2 })
TestObjectIdentifier4 ::= OBJECT IDENTIFIER ({ iso 3 6 1 })
TestObjectIdentifier5 ::= OBJECT IDENTIFIER (testObjectIdentifier2)

testRelativeOID1 RELATIVE-OID ::= { 4 1 }
testRelativeOID2 RELATIVE-OID ::= { testRelativeOID1 11 2 }

TestRelativeOID1 ::= RELATIVE-OID ({ 3 6 1 } | { 3 6 2 })
TestRelativeOID2 ::= RELATIVE-OID (({ 3 6 1 } | { 3 6 2 }) EXCEPT { 3 6 2 })
TestRelativeOID3 ::= RELATIVE-OID (({ 3 6 1 } | { 3 6 2 }) ^ { 3 6 2 })
TestRelativeOID4 ::= RELATIVE-OID ({ 3 6 1 })
TestRelativeOID5 ::= RELATIVE-OID (testRelativeOID2)

testOidIri1 OID-IRI ::= "/ISO/a/b/f"

TestOidIri1 ::= OID-IRI ("/ISO/a/b/c" | "/ISO/a/b/d")
TestOidIri2 ::= OID-IRI (("/ISO/a/b/c" | "/ISO/a/b/d") EXCEPT "/ISO/a/b/c")
TestOidIri3 ::= OID-IRI (("/ISO/a/b/c" | "/ISO/a/b/d") ^ "/ISO/a/b/c")
TestOidIri4 ::= OID-IRI ("/ISO/a/b/e")
TestOidIri5 ::= OID-IRI (testOidIri1)

END
