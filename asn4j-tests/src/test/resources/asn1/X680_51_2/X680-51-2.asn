X680-51-2 DEFINITIONS ::=
BEGIN

bitStringValue BIT STRING ::= '100'B

TestBitString1 ::= BIT STRING (ALL EXCEPT bitStringValue)
TestBitString2 ::= BIT STRING (('000'B | '001'B | '010'B | '011'B | bitStringValue | '101'B | '110'B | '111'B) EXCEPT '010'B)
TestBitString3 ::= BIT STRING ((('000'B | '001'B | '010'B | '011'B) ^ ('001'B | '010'B | '011'B)) EXCEPT '010'B)
TestBitString4 ::= BIT STRING (('000'B | '001'B | '010'B) ^ ('001'B | '010'B), ...)
-- TestBitString5 must be extensible
TestBitString5 ::= TestBitString4
-- TestBitString6 must not be extensible
TestBitString6 ::= TestBitString4 (ALL EXCEPT '001'B)

TestBoolean1 ::= BOOLEAN (ALL EXCEPT TRUE)
TestBoolean2 ::= BOOLEAN (TRUE)
TestBoolean3 ::= BOOLEAN (FALSE)
TestBoolean4 ::= BOOLEAN (TRUE | FALSE)
TestBoolean5 ::= BOOLEAN ((TRUE | FALSE) ^ TRUE)
TestBoolean6 ::= TestBoolean4 (ALL EXCEPT FALSE)

TestEnumeration1 ::= ENUMERATED {
        a, b, c, d
}

TestEnumeration2 ::= TestEnumeration1 (a | b)
TestEnumeration3 ::= TestEnumeration1 ((a | b | c) ^ (b | c | d))
TestEnumeration4 ::= TestEnumeration1 (ALL EXCEPT d)

TestInteger1 ::= INTEGER (1 | 2)
TestInteger2 ::= INTEGER (ALL EXCEPT 0)
TestInteger3 ::= INTEGER (((1 | 2 | 3) ^ (2 | 3)) EXCEPT 3)

TestNull1 ::= NULL (NULL)
TestNull2 ::= NULL (ALL EXCEPT NULL)
TestNull3 ::= NULL ((NULL ^ NULL) EXCEPT NULL)

testObjectIdentifier1 OBJECT IDENTIFIER ::= { itu-t 4 }
testObjectIdentifier2 OBJECT IDENTIFIER ::= { testObjectIdentifier1 11 2 }

TestObjectIdentifier1 ::= OBJECT IDENTIFIER ({ 1 3 6 1 } | { 1 3 6 2 })
TestObjectIdentifier2 ::= OBJECT IDENTIFIER (({ 1 3 6 1 } | { 1 3 6 2 }) EXCEPT { 1 3 6 2 })
TestObjectIdentifier3 ::= OBJECT IDENTIFIER (({ 1 3 6 1 } | { 1 3 6 2 }) ^ { 1 3 6 2 })
TestObjectIdentifier4 ::= OBJECT IDENTIFIER ({ iso 3 6 1 })
TestObjectIdentifier5 ::= OBJECT IDENTIFIER (testObjectIdentifier2)

testRelativeOID1 RELATIVE-OID ::= { 4 1 }
testRelativeOID2 RELATIVE-OID ::= { testRelativeOID1 11 2 }

TestRelativeOID1 ::= RELATIVE-OID ({ 3 6 1 } | { 3 6 2 })
TestRelativeOID2 ::= RELATIVE-OID (({ 3 6 1 } | { 3 6 2 }) EXCEPT { 3 6 2 })
TestRelativeOID3 ::= RELATIVE-OID (({ 3 6 1 } | { 3 6 2 }) ^ { 3 6 2 })
TestRelativeOID4 ::= RELATIVE-OID ({ 3 6 1 })
TestRelativeOID5 ::= RELATIVE-OID (testRelativeOID2)

testOidIri1 OID-IRI ::= "/ISO/a/b/f"

TestOidIri1 ::= OID-IRI ("/ISO/a/b/c" | "/ISO/a/b/d")
TestOidIri2 ::= OID-IRI (("/ISO/a/b/c" | "/ISO/a/b/d") EXCEPT "/ISO/a/b/c")
TestOidIri3 ::= OID-IRI (("/ISO/a/b/c" | "/ISO/a/b/d") ^ "/ISO/a/b/c")
TestOidIri4 ::= OID-IRI ("/ISO/a/b/e")
TestOidIri5 ::= OID-IRI (testOidIri1)

testRelativeOidIri1 RELATIVE-OID-IRI ::= "a/b/f"

TestRelativeOidIri1 ::= RELATIVE-OID-IRI ("a/b/c" | "a/b/d")
TestRelativeOidIri2 ::= RELATIVE-OID-IRI (("a/b/c" | "a/b/d") EXCEPT "a/b/c")
TestRelativeOidIri3 ::= RELATIVE-OID-IRI (("a/b/c" | "a/b/d") ^ "a/b/c")
TestRelativeOidIri4 ::= RELATIVE-OID-IRI ("a/b/e")
TestRelativeOidIri5 ::= RELATIVE-OID-IRI (testRelativeOidIri1)

testOctetString1 OCTET STRING ::= '37'H

TestOctetString1 ::= OCTET STRING ('0101'B | '37'H)
TestOctetString2 ::= OCTET STRING (('0101'B | '37'H) EXCEPT testOctetString1)
TestOctetString3 ::= OCTET STRING (('0101'B | '37'H) ^ testOctetString1)
TestOctetString4 ::= OCTET STRING (testOctetString1)

testInteger1 INTEGER ::= 12
testSetOf1 SET OF INTEGER ::= {1, 2, 3}

TestSetOfType1 ::= SET OF INTEGER

TestSetOf1 ::= SET ({}) OF INTEGER
TestSetOf2 ::= SET ({23}) OF INTEGER
TestSetOf3 ::= SET ({23} | {47}) OF INTEGER
TestSetOf4 ::= SET ({testInteger1} | {2, 3}) OF INTEGER
TestSetOf5 ::= SET (testSetOf1) OF INTEGER
TestSetOf6 ::= TestSetOfType1 (testSetOf1)

TestSetOfBitString1 ::= SET ({'0111'B}) OF BIT STRING

TestSetOfBoolean1 ::= SET ({TRUE}) OF BOOLEAN

TestSetOfEnumeration1 ::= SET ({a}) OF TestEnumeration1
TestSetOfEnumeration2 ::= SET ({a, c}) OF TestEnumeration1

TestSetOfOctetString1 ::= SET ({'0101'B}) OF OCTET STRING
TestSetOfOctetString2 ::= SET ({'37'H}) OF TestOctetString1

TestNull4 ::= NULL

TestSetOfNull1 ::= SET ({}) OF NULL
TestSetOfNull2 ::= SET ({NULL}) OF TestNull4

TestSetOfObjectIdentifier1 ::= SET ({{ 1 3 6 1 }}) OF OBJECT IDENTIFIER
TestSetOfObjectIdentifier2 ::= SET ({{ 1 3 6 2 }}) OF TestObjectIdentifier1

TestSetOfRelativeOID1 ::= SET ({{ 4 1 }}) OF RELATIVE-OID
TestSetOfRelativeOID2 ::= SET ({{ 3 6 2 }}) OF TestRelativeOID1

TestSetOfOidIri1 ::= SET ({"/ISO/a/b/f"}) OF OID-IRI
TestSetOfOidIri2 ::= SET ({"/ISO/a/b/c"}) OF TestOidIri1

TestSetOfRelativeOidIri1 ::= SET ({"a/b/d"}) OF RELATIVE-OID-IRI
TestSetOfRelativeOidIri2 ::= SET ({"a/b/c"}) OF TestRelativeOidIri1

TestSequenceOfEnumeration1 ::= SEQUENCE ({a}) OF TestEnumeration1
TestSequenceOfEnumeration2 ::= SEQUENCE ({a, c}) OF TestEnumeration1

TestSequence1 ::= SEQUENCE {
	a INTEGER,
	b BOOLEAN
} ({a testInteger1, b TRUE})
TestSequence2 ::= SEQUENCE {
   a SET OF INTEGER,
   b SET OF TestInteger2
} ({a {1, 2}, b {4, 5}})
TestSequence3 ::= SEQUENCE {
   a SEQUENCE {
       b INTEGER,
       c BOOLEAN
   },
   d SET OF TestInteger2
} ({a {b 1, c TRUE}, d {4, 5}})

testChoice1 TestChoice1 ::= a: testInteger1

TestChoice1 ::= CHOICE {
   a INTEGER,
   b BOOLEAN
} (testChoice1 | b: TRUE)
TestChoice2 ::= CHOICE {
   a SET OF INTEGER
} (a: {1, 2, 3})
TestChoice3 ::= CHOICE {
   a SEQUENCE {
       b INTEGER,
       c BOOLEAN
   },
   d OCTET STRING
} (a: {b 1, c TRUE} | d: 'BEEF'H)

TestVisibleString1 ::= VisibleString ("abc")

TestISO646String1 ::= ISO646String ("abc")

TestGeneralString1 ::= GeneralString ("abc")

TestGraphicString1 ::= GraphicString ("abc")

TestIA5String1 ::= IA5String ("abc")

TestVideotexString1 ::= VideotexString ("abc")

TestTeletexString1 ::= TeletexString ("abc")

TestT61String1 ::= T61String ("abc")

TestPrintableString1 ::= PrintableString ("abc")

TestNumericString1 ::= NumericString ("123")

TestUTF8String1 ::= UTF8String ("abc")

TestUniversalString1 ::= UniversalString ("abc")

TestBMPString1 ::= BMPString ("abc")

END
