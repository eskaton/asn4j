X680-41 DEFINITIONS ::=
BEGIN

TestVisibleString1 ::= VisibleString

TestNumericString1 ::= NumericString

TestPrintableString1 ::= PrintableString

TestTeletexString1 ::= TeletexString

TestT61String1 ::= T61String

TestVideotexString1 ::= VideotexString

TestIA5String1 ::= IA5String

TestGraphicString1 ::= GraphicString

TestGeneralString1 ::= GeneralString

TestUniversalString1 ::= UniversalString

TestUTF8String1 ::= UTF8String

TestBMPString1 ::= BMPString

END
