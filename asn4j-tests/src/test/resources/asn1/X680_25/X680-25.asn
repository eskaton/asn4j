X680-25 DEFINITIONS ::=
BEGIN

TestSequence0 ::= SEQUENCE {
	a BOOLEAN
}

TestSequence1 ::= SEQUENCE {
	a INTEGER,
	b BOOLEAN,
	c OCTET STRING 
}

TestSequence2 ::= SEQUENCE {
	a INTEGER,
	b BOOLEAN OPTIONAL,
	c OCTET STRING 
}

TestBitString1 ::= BIT STRING {
  test-a(0),
  test-b(one),
  test-c(two)
}

TestBitString2 ::= TestBitString1

TestNamedInteger2 ::= INTEGER {
	two(2)
}

one INTEGER ::= 1

two TestNamedInteger2 ::= two

testBitString2 TestBitString2 ::= { test-a, test-b }

TestSequence3 ::= SEQUENCE {
	a INTEGER,
	b BOOLEAN,
	c OCTET STRING DEFAULT 'ABC'H,
	d BIT STRING DEFAULT '000100100011010001010110011110011010101111001101111011110000'B,
	e BIT STRING DEFAULT '0123456789ABCDEF0123456789ABCDEF0123456789ABCDEF0123456789ABCDEF'H,
	f BIT STRING DEFAULT testBitString2,
	g TestBitString2 DEFAULT { test-a, test-c },
	h TestBitString2 DEFAULT { }
}

intValue INTEGER ::= 4711

TestSequence4 ::= SEQUENCE {
	a INTEGER DEFAULT intValue,
	b BOOLEAN,
	c OCTET STRING
}

TestSequence5 ::= SEQUENCE {
	a INTEGER DEFAULT 23,
	...,
	z INTEGER,
	...,
	b BOOLEAN
}

TestSequence6 ::= SEQUENCE {
	COMPONENTS OF TestSequence5,
	c BOOLEAN
}

TestSequence7 ::= SEQUENCE {
	a INTEGER,
	...,
	[[1: c INTEGER]],
	[[2: d BOOLEAN]],
	...,
	b INTEGER
}

TestSequence8 ::= SEQUENCE {
    childSequence SEQUENCE {
       a INTEGER
   }
}

TestSequence9 ::= SEQUENCE {
    childEnumerated ENUMERATED {a, b, c}
}

TestSequence10 ::= SEQUENCE {
	a INTEGER,
	...,
	[[c INTEGER,
	  d BOOLEAN]],
	...,
	b INTEGER
}

TestSequence11 ::= SEQUENCE {
    childSequence SEQUENCE {
       a INTEGER,
       ...,
       b BOOLEAN
   }
}

TestSequence12 ::= SEQUENCE {
    childInteger INTEGER {a(1), b(3), c(5)}
}

-- Test defaults for all types

TestBoolean ::= BOOLEAN

testBooleanValue1 BOOLEAN ::= TRUE

testBooleanValue2 BOOLEAN ::= FALSE

testBooleanValue3 TestBoolean ::= TRUE

TestSequenceDefaults1 ::= SEQUENCE {
    testBoolean1 BOOLEAN DEFAULT testBooleanValue1,
    testBoolean2 BOOLEAN DEFAULT testBooleanValue2,
    testBoolean3 TestBoolean DEFAULT testBooleanValue3,
    testBoolean4 BOOLEAN DEFAULT FALSE
}

TestEnumeration ::= ENUMERATED {
	a, b
}

testEnumerationValue1 TestEnumeration ::= a

testEnumerationValue2 TestEnumeration ::= testEnumerationValue1

TestSequenceDefaults2 ::= SEQUENCE {
    testEnumeration1 TestEnumeration DEFAULT b,
    testEnumeration2 TestEnumeration DEFAULT testEnumerationValue1,
    testEnumeration3 TestEnumeration DEFAULT testEnumerationValue2
}

TestOctetString ::= OCTET STRING

testOctetStringValue1 TestOctetString ::= '01AF'H

testOctetStringValue2 TestOctetString ::= testOctetStringValue1

TestSequenceDefaults3 ::= SEQUENCE {
    testOctetString1 OCTET STRING DEFAULT testOctetStringValue1,
    testOctetString2 TestOctetString DEFAULT testOctetStringValue1,
    testOctetString3 TestOctetString DEFAULT testOctetStringValue2,
    testOctetString4 TestOctetString DEFAULT '0101'B
}

testObjectIdentifierValue1 OBJECT IDENTIFIER ::= { 1 3 6 1 }

TestSequenceDefaults4 ::= SEQUENCE {
    testObjectIdentifier1 OBJECT IDENTIFIER DEFAULT testObjectIdentifierValue1
}

testRelativeOIDValue1 RELATIVE-OID ::= { 3 6 1 }

TestSequenceDefaults5 ::= SEQUENCE {
    testRelativeOID1 RELATIVE-OID DEFAULT testRelativeOIDValue1
}

testOidIriValue1 OID-IRI ::= "/ISO/Registration-Authority/19785.CBEFF/Organizations"

TestSequenceDefaults6 ::= SEQUENCE {
    testOidIri1 OID-IRI DEFAULT testOidIriValue1,
    testOidIri2 OID-IRI DEFAULT "/ISO/Registration-Authority/Test"
}

testRelativeOidIriValue1 RELATIVE-OID-IRI ::= "Registration-Authority/19785.CBEFF/Organizations"

TestSequenceDefaults7 ::= SEQUENCE {
    testRelativeOidIri1 RELATIVE-OID-IRI DEFAULT testRelativeOidIriValue1,
    testRelativeOidIri2 RELATIVE-OID-IRI DEFAULT "Registration-Authority/Test"
}

testIntegerValue1 INTEGER ::= 4711

TestSequenceDefaults8 ::= SEQUENCE {
    testInteger1 INTEGER DEFAULT testIntegerValue1,
    testInteger2 INTEGER DEFAULT 23
}

testMantissa1 INTEGER ::= 7
testRealValue1 REAL ::= 12.78
testRealValue2 REAL ::= { mantissa 5, base 2, exponent 3}
testRealValue3 REAL ::= { mantissa testMantissa1, base 2, exponent 3}

TestReal1 ::= REAL

TestSequenceDefaults9 ::= SEQUENCE {
    testReal1 REAL DEFAULT testRealValue1,
    testReal2 REAL DEFAULT testRealValue2,
    testReal3 REAL DEFAULT testRealValue3,
    testReal4 REAL DEFAULT 12.78e-5,
    testReal5 REAL DEFAULT MINUS-INFINITY,
    testReal6 REAL DEFAULT PLUS-INFINITY,
    testReal7 REAL DEFAULT NOT-A-NUMBER,
    testReal8 TestReal1 DEFAULT NOT-A-NUMBER
}

TestNull1 ::= NULL

TestSequenceDefaults10 ::= SEQUENCE {
    test-Null1 NULL DEFAULT NULL,
    test-Null2 TestNull1 DEFAULT NULL
}

testSequenceValue1 TestSequence2 ::= { a 1, c 'ABC'H }

TestSequenceDefaults11 ::= SEQUENCE {
	a SEQUENCE {
	    a INTEGER,
	    b BOOLEAN
	} DEFAULT { a 1, b FALSE },
	b TestSequence2 DEFAULT testSequenceValue1
}

TestSet1 ::= SET {
    a BOOLEAN,
    b INTEGER
}

testSetValue1 TestSet1 ::= { b 1, a FALSE}

TestSequenceDefaults12 ::= SEQUENCE {
	a SET {
	    a INTEGER,
	    b BOOLEAN
	} DEFAULT { b TRUE, a 2 },
	b TestSet1 DEFAULT testSetValue1
}

TestSequenceOf1 ::= SEQUENCE OF INTEGER

testSequenceOfValue1 TestSequenceOf1 ::= { 1, 3, 5 }

TestSequenceDefaults13 ::= SEQUENCE {
	a SEQUENCE OF BOOLEAN DEFAULT { TRUE, FALSE },
	b TestSequenceOf1 DEFAULT testSequenceOfValue1
}

TestSetOf1 ::= SET OF INTEGER

testSetOfValue1 TestSetOf1 ::= { 2, 4, 6 }

TestSequenceDefaults14 ::= SEQUENCE {
	a SET OF BOOLEAN DEFAULT { FALSE, FALSE },
	b TestSetOf1 DEFAULT testSetOfValue1
}

TestChoice1 ::= CHOICE {
    a BOOLEAN,
    b INTEGER
}

TestSequenceDefaults15 ::= SEQUENCE {
    a CHOICE {
        a INTEGER,
        b BOOLEAN
    } DEFAULT a: 25,
    b TestChoice1 DEFAULT a: TRUE
}

TestVisibleString1 ::= VisibleString

TestSequenceDefaults16 ::= SEQUENCE {
    a VisibleString DEFAULT "test1",
    b TestVisibleString1 DEFAULT "test2"
}

TestGeneralizedTime1 ::= GeneralizedTime

TestSequenceDefaults17 ::= SEQUENCE {
    a GeneralizedTime DEFAULT "19851106210627.3Z",
    b TestGeneralizedTime1 DEFAULT "19851106210627.3-0500"
}

TestUTCTime1 ::= UTCTime

TestSequenceDefaults18 ::= SEQUENCE {
    a UTCTime DEFAULT "8201021200Z",
    b TestUTCTime1 DEFAULT "8201020700-0500"
}

TestNumericString1 ::= NumericString

TestSequenceDefaults19 ::= SEQUENCE {
    a NumericString DEFAULT "1234",
    b TestNumericString1 DEFAULT "5678"
}

TestPrintableString1 ::= PrintableString

TestSequenceDefaults20 ::= SEQUENCE {
    a PrintableString DEFAULT "abCD",
    b TestPrintableString1 DEFAULT "5678"
}

TestIA5String1 ::= IA5String

TestSequenceDefaults21 ::= SEQUENCE {
    a IA5String DEFAULT {"abCD", {2, 2}, {2, 7}, {5, 12}, {0, 10}},
    b TestIA5String1 DEFAULT "5678"
}

TestGraphicString1 ::= GraphicString

TestSequenceDefaults22 ::= SEQUENCE {
    a GraphicString DEFAULT "abCD",
    b TestGraphicString1 DEFAULT "5678"
}

TestTeletexString1 ::= TeletexString

TestSequenceDefaults23 ::= SEQUENCE {
    a TeletexString DEFAULT "abCD",
    b TestTeletexString1 DEFAULT "5678"
}

TestT61String1 ::= T61String

TestSequenceDefaults24 ::= SEQUENCE {
    a T61String DEFAULT "abCD",
    b TestT61String1 DEFAULT "5678"
}

TestVideotexString1 ::= VideotexString

TestSequenceDefaults25 ::= SEQUENCE {
    a VideotexString DEFAULT "abCD",
    b TestVideotexString1 DEFAULT "5678"
}

TestGeneralString1 ::= GeneralString

TestSequenceDefaults26 ::= SEQUENCE {
    a GeneralString DEFAULT "abCD",
    b TestGeneralString1 DEFAULT "5678"
}

TestUniversalString1 ::= UniversalString

TestSequenceDefaults27 ::= SEQUENCE {
    a UniversalString DEFAULT {"abCD", {0, 1, 246, 2}},
    b TestUniversalString1 DEFAULT "5678"
}

TestUTF8String1 ::= UTF8String

TestSequenceDefaults28 ::= SEQUENCE {
    a UTF8String DEFAULT {"abCD", {0, 1, 246, 2}},
    b TestUTF8String1 DEFAULT "5678"
}

TestBMPString1 ::= BMPString

TestSequenceDefaults29 ::= SEQUENCE {
    a BMPString DEFAULT {"abCDü"},
    b TestBMPString1 DEFAULT "5678"
}

END
