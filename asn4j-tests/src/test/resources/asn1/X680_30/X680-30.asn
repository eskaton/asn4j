X680-30 DEFINITIONS ::=
BEGIN

SelectedType1 ::= c < TestSelectionChoiceType1

TestSelectionSetType ::= SET {
   a a < TestSelectionChoiceType1 OPTIONAL,
   b b < TestSelectionChoiceType1 OPTIONAL,
   c SelectedType1 OPTIONAL
}

TestSelectionChoiceType1 ::= CHOICE {
   a  [0] IMPLICIT INTEGER,
   b  [1] IMPLICIT VisibleString,
   c  [2] IMPLICIT BOOLEAN
 }

END
