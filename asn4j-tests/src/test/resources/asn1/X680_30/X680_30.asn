X680-30 DEFINITIONS ::=
BEGIN

SelectedType ::= c < ChoiceType

SetType ::= SET {
   a a < ChoiceType OPTIONAL,
   b b < ChoiceType OPTIONAL,
   c SelectedType OPTIONAL
}

ChoiceType ::= CHOICE {
   a  [0] IMPLICIT INTEGER,
   b  [1] IMPLICIT VisibleString,
   c  [2] IMPLICIT BOOLEAN
 }

END
