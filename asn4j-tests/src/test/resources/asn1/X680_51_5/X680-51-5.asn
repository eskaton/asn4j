X680-51-5 DEFINITIONS ::=
BEGIN

max INTEGER ::= 3

TestBitString1 ::= BIT STRING (SIZE(MIN..MAX))
TestBitString2 ::= BIT STRING (SIZE(4..MAX))
TestBitString3 ::= BIT STRING (SIZE(MIN..4))
TestBitString4 ::= BIT STRING (SIZE(2..6))
TestBitString5 ::= BIT STRING (SIZE(4..MAX) | SIZE(2..8))
TestBitString6 ::= BIT STRING (SIZE(4..MAX) ^ SIZE(2..8))
TestBitString7 ::= BIT STRING (SIZE(4..MAX) EXCEPT SIZE(8..16))
TestBitString8 ::= BIT STRING (SIZE(4..MAX)) (SIZE(MIN..8))
TestBitString9 ::= BIT STRING (SIZE(4..12), ..., SIZE(13..16))
TestBitString10 ::= BIT STRING (SIZE (2))
TestBitStringSize ::= INTEGER (ALL EXCEPT 1)
TestBitString11 ::= BIT STRING (SIZE (INCLUDES TestBitStringSize))
TestBitString12 ::= BIT STRING (SIZE (INTEGER EXCEPT 2))
TestBitString13 ::= BIT STRING (SIZE(0..max))

TestOctetString1 ::= OCTET STRING (SIZE(MIN..MAX))
TestOctetString2 ::= OCTET STRING (SIZE(4..MAX))
TestOctetString3 ::= OCTET STRING (SIZE(MIN..4))
TestOctetString4 ::= OCTET STRING (SIZE(2..6))
TestOctetString5 ::= OCTET STRING (SIZE(4..MAX) | SIZE(2..8))
TestOctetString6 ::= OCTET STRING (SIZE(4..MAX) ^ SIZE(2..8))
TestOctetString7 ::= OCTET STRING (SIZE(4..MAX) EXCEPT SIZE(8..16))
TestOctetString8 ::= OCTET STRING (SIZE(4..MAX)) (SIZE(MIN..8))
TestOctetString9 ::= OCTET STRING (SIZE(4..12), ..., SIZE(13..16))
TestOctetString10 ::= OCTET STRING (SIZE (2))
TestOctetStringSize ::= INTEGER (ALL EXCEPT 1)
TestOctetString11 ::= OCTET STRING (SIZE (INCLUDES TestOctetStringSize))
TestOctetString12 ::= OCTET STRING (SIZE (INTEGER EXCEPT 2))

TestSetOf1 ::= SET (SIZE(1..2)) OF INTEGER
TestSetOf2 ::= SET (SIZE(1) | SIZE(2..3)) OF INTEGER
TestSetOf3 ::= SET SIZE (2) OF INTEGER

TestSequenceOf1 ::= SEQUENCE (SIZE(1..2)) OF INTEGER
TestSequenceOf2 ::= SEQUENCE SIZE (2) OF INTEGER

TestVisibleString1 ::= VisibleString (SIZE(1..2))

TestISO646String1 ::= ISO646String (SIZE(1..2))

TestGeneralString1 ::= GeneralString (SIZE(1..2))

TestGraphicString1 ::= GraphicString (SIZE(1..2))

TestIA5String1 ::= IA5String (SIZE(1..2))

TestVideotexString1 ::= VideotexString (SIZE(1..2))

TestTeletexString1 ::= TeletexString (SIZE(1..2))

TestT61String1 ::= T61String (SIZE(1..2))

TestPrintableString1 ::= PrintableString (SIZE(1..2))

TestNumericString1 ::= NumericString (SIZE(1..2))

TestUTF8String1 ::= UTF8String (SIZE(1..2))

TestUniversalString1 ::= UniversalString (SIZE(1..2))

TestBMPString1 ::= BMPString (SIZE(1..2))

END
