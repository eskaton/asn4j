X681 DEFINITIONS ::=
BEGIN

TEST-FIXED-TYPE-VALUES ::= CLASS {
    &bitStringField        BIT STRING,
    &booleanField          BOOLEAN,
    &enumField             ENUMERATED {a, b, c},
    &intField              INTEGER {a(1), b(3), c(5)},
    &nullField             NULL,
    &octetStringField      OCTET STRING,
    &visibleStringField    VisibleString,
    &generalStringField    GeneralString,
    &graphicStringField    GraphicString,
    &ia5StringField        IA5String,
    &videotexStringField   VideotexString,
    &teletexStringField    TeletexString,
    &printableStringField  PrintableString,
    &numericStringField    NumericString,
    &utf8StringField       UTF8String,
    &universalStringField  UniversalString,
    &bmpStringField        BMPString,
    &sequenceOfField       SEQUENCE OF INTEGER,
    &setOfField            SET OF INTEGER,
    &sequenceField         SEQUENCE { a INTEGER, b BOOLEAN },
    &setField              SET { a INTEGER, b BOOLEAN },
    &choiceField           CHOICE { a INTEGER, b BOOLEAN },
    &objectIdentifierField OBJECT IDENTIFIER,
    &relativeOidField      RELATIVE-OID,
    &oidIriField           OID-IRI,
    &relativeOidIriField   RELATIVE-OID-IRI,
    &realField             REAL
}

TestFixedTypeValuesSet TEST-FIXED-TYPE-VALUES ::= {
    { &bitStringField        '0101'B,
      &booleanField          TRUE,
      &enumField             a,
      &intField              c,
      &nullField             NULL,
      &octetStringField      '0BD9'H,
      &visibleStringField    "abc",
      &generalStringField    "abc",
      &graphicStringField    "abc",
      &ia5StringField        "abc",
      &videotexStringField   "abc",
      &teletexStringField    "abc",
      &printableStringField  "abc",
      &numericStringField    "123",
      &utf8StringField       "äöü",
      &universalStringField  "äöü",
      &bmpStringField        "äöü",
      &sequenceOfField       {1, 2, 3},
      &setOfField            {1, 2, 3},
      &sequenceField         {a 1, b TRUE},
      &setField              {a 1, b TRUE},
      &choiceField           b: TRUE,
      &objectIdentifierField { 1 3 6 1 },
      &relativeOidField      { 3 6 1 },
      &oidIriField           "/ISO/a/b/a",
      &relativeOidIriField   "a/b/a",
      &realField             2.3
    }
}

TestSequence1 ::= SEQUENCE {
   bitStringField TEST-FIXED-TYPE-VALUES.&bitStringField
}

TestSequence2 ::= SEQUENCE {
   booleanField TEST-FIXED-TYPE-VALUES.&booleanField
}

TestSequence3 ::= SEQUENCE {
   enumField TEST-FIXED-TYPE-VALUES.&enumField
}

TestSequence4 ::= SEQUENCE {
   intField TEST-FIXED-TYPE-VALUES.&intField
}

TestSequence5 ::= SEQUENCE {
   nullField TEST-FIXED-TYPE-VALUES.&nullField
}

TestSequence6 ::= SEQUENCE {
   octetStringField TEST-FIXED-TYPE-VALUES.&octetStringField
}

TestSequence7 ::= SEQUENCE {
   visibleStringField TEST-FIXED-TYPE-VALUES.&visibleStringField
}

TestSequence8 ::= SEQUENCE {
   generalStringField TEST-FIXED-TYPE-VALUES.&generalStringField
}

TestSequence9 ::= SEQUENCE {
   graphicStringField TEST-FIXED-TYPE-VALUES.&graphicStringField
}

TestSequence10 ::= SEQUENCE {
   ia5StringField TEST-FIXED-TYPE-VALUES.&ia5StringField
}

TestSequence11 ::= SEQUENCE {
   videotexStringField TEST-FIXED-TYPE-VALUES.&videotexStringField
}

TestSequence12 ::= SEQUENCE {
   teletexStringField TEST-FIXED-TYPE-VALUES.&teletexStringField
}

TestSequence13 ::= SEQUENCE {
   printableStringField TEST-FIXED-TYPE-VALUES.&printableStringField
}

TestSequence14 ::= SEQUENCE {
   numericStringField TEST-FIXED-TYPE-VALUES.&numericStringField
}

TestSequence15 ::= SEQUENCE {
   utf8StringField TEST-FIXED-TYPE-VALUES.&utf8StringField
}

TestSequence16 ::= SEQUENCE {
   universalStringField TEST-FIXED-TYPE-VALUES.&universalStringField
}

TestSequence17 ::= SEQUENCE {
   bmpStringField TEST-FIXED-TYPE-VALUES.&bmpStringField
}

TestSequence18 ::= SEQUENCE {
   sequenceOfField TEST-FIXED-TYPE-VALUES.&sequenceOfField
}

TestSequence19 ::= SEQUENCE {
   setOfField TEST-FIXED-TYPE-VALUES.&setOfField
}

TestSequence20 ::= SEQUENCE {
   sequenceField TEST-FIXED-TYPE-VALUES.&sequenceField
}

TestSequence21 ::= SEQUENCE {
   setField TEST-FIXED-TYPE-VALUES.&setField
}

TestSequence22 ::= SEQUENCE {
   choiceField TEST-FIXED-TYPE-VALUES.&choiceField
}

TestSequence23 ::= SEQUENCE {
   objectIdentifierField TEST-FIXED-TYPE-VALUES.&objectIdentifierField
}

TestSequence24 ::= SEQUENCE {
   relativeOidField TEST-FIXED-TYPE-VALUES.&relativeOidField
}

TestSequence25 ::= SEQUENCE {
   oidIriField TEST-FIXED-TYPE-VALUES.&oidIriField
}

TestSequence26 ::= SEQUENCE {
   relativeOidIriField TEST-FIXED-TYPE-VALUES.&relativeOidIriField
}

TestSequence27 ::= SEQUENCE {
   realField TEST-FIXED-TYPE-VALUES.&realField
}


TEST-TYPE ::= CLASS {
    &TypeField
}

TestSequence101 ::= SEQUENCE {
   typeField TEST-TYPE.&TypeField
}

TestSequence102 ::= SEQUENCE {
   typeField TEST-TYPE.&TypeField,
   intField  INTEGER
}

TestSet101 ::= SET {
   typeField TEST-TYPE.&TypeField
}

TestSet102 ::= SET {
   intField        INTEGER,
   typeField1 [23] TEST-TYPE.&TypeField,
   typeField2 [24] TEST-TYPE.&TypeField
}

TestSet103 ::= SET {
   choiceField CHOICE {
                  typeField TEST-TYPE.&TypeField
               }
}

TestChoice101 ::= CHOICE {
   typeField TEST-TYPE.&TypeField
}

TestChoice102 ::= CHOICE {
   typeField1 [23] TEST-TYPE.&TypeField,
   typeField2 [24] TEST-TYPE.&TypeField
}


TEST-VARIABLE-TYPE-VALUES ::= CLASS {
    &bitStringField        &BitStringField        DEFAULT '0101'B,
    &booleanField          &BooleanField          DEFAULT TRUE,
    &enumField             &EnumField             DEFAULT a,
    &intField              &IntField              DEFAULT c,
    &nullField             &NullField             DEFAULT NULL,
    &octetStringField      &OctetStringField      DEFAULT '0BD9'H,
    &visibleStringField    &VisibleStringField    DEFAULT "abc",
    &generalStringField    &GeneralStringField    DEFAULT "abc",
    &graphicStringField    &GraphicStringField    DEFAULT "abc",
    &ia5StringField        &Ia5StringField        DEFAULT "abc",
    &videotexStringField   &VideotexStringField   DEFAULT "abc",
    &teletexStringField    &TeletexStringField    DEFAULT "abc",
    &printableStringField  &PrintableStringField  DEFAULT "abc",
    &numericStringField    &NumericStringField    DEFAULT "123",
    &utf8StringField       &Utf8StringField       DEFAULT "äöü",
    &universalStringField  &UniversalStringField  DEFAULT "äöü",
    &bmpStringField        &BmpStringField        DEFAULT "äöü",
    &sequenceOfField       &SequenceOfField       DEFAULT {1, 2, 3},
    &setOfField            &SetOfField            DEFAULT {1, 2, 3},
    &sequenceField         &SequenceField         DEFAULT {a 1, b TRUE},
    &setField              &SetField              DEFAULT {a 1, b TRUE},
    &choiceField           &ChoiceField           DEFAULT b: TRUE,
    &objectIdentifierField &ObjectIdentifierField DEFAULT { 1 3 6 1 },
    &relativeOidField      &RelativeOidField      DEFAULT { 3 6 1 },
    &oidIriField           &OidIriField           DEFAULT "/ISO/a/b/a",
    &relativeOidIriField   &RelativeOidIriField   DEFAULT "a/b/a",
    &realField             &RealField             DEFAULT 2.3,
    &BitStringField        DEFAULT BIT STRING,
    &BooleanField          DEFAULT BOOLEAN,
    &EnumField             DEFAULT ENUMERATED {a, b, c},
    &IntField              DEFAULT INTEGER {a(1), b(3), c(5)},
    &NullField             DEFAULT NULL,
    &OctetStringField      DEFAULT OCTET STRING,
    &VisibleStringField    DEFAULT VisibleString,
    &GeneralStringField    DEFAULT GeneralString,
    &GraphicStringField    DEFAULT GraphicString,
    &Ia5StringField        DEFAULT IA5String,
    &VideotexStringField   DEFAULT VideotexString,
    &TeletexStringField    DEFAULT TeletexString,
    &PrintableStringField  DEFAULT PrintableString,
    &NumericStringField    DEFAULT NumericString,
    &Utf8StringField       DEFAULT UTF8String,
    &UniversalStringField  DEFAULT UniversalString,
    &BmpStringField        DEFAULT BMPString,
    &SequenceOfField       DEFAULT SEQUENCE OF INTEGER,
    &SetOfField            DEFAULT SET OF INTEGER,
    &SequenceField         DEFAULT SEQUENCE { a INTEGER, b BOOLEAN },
    &SetField              DEFAULT SET { a INTEGER, b BOOLEAN },
    &ChoiceField           DEFAULT CHOICE { a INTEGER, b BOOLEAN },
    &ObjectIdentifierField DEFAULT OBJECT IDENTIFIER,
    &RelativeOidField      DEFAULT RELATIVE-OID,
    &OidIriField           DEFAULT OID-IRI,
    &RelativeOidIriField   DEFAULT RELATIVE-OID-IRI,
    &RealField             DEFAULT REAL
}

TestVariableTypeValuesSet TEST-VARIABLE-TYPE-VALUES ::= {
    {}
}

END
