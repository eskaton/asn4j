X680-27 DEFINITIONS ::=
BEGIN

TestSet1 ::= SET {
	a [0] INTEGER,
	b [1] INTEGER OPTIONAL
}

TestSet2 ::= SET {
	a [0] INTEGER,
	b [1] OCTET STRING,
	c INTEGER OPTIONAL
}

TestSet3 ::= SET {
    a [0] SET {
        b INTEGER,
        c BOOLEAN
    } DEFAULT { b 1, c TRUE },
    b [1] TestSet2 DEFAULT { a 1, b 'ABC'H }
}

END
